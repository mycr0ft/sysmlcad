// Simple box — SysMLv2 with explicit SI unit annotations
package SimpleBox {
    part myBox {
        attribute length = 100.0 [mm];
        attribute width  = 50.0 [mm];
        attribute height = 30.0 [mm];
    }
}
